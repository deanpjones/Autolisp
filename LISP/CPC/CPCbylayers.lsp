;;;Runs script to change all objects color, ltype and lweight to BYLAYER.
;;;Created by Dean Jones Mar. 23, 2007.

(defun c:CPCbylayers ()

(command "script" "S:\\BR-S\\gsGRP\\GROUP\\ENGCAD\\00.000 CAD Management\\700\\780 CAD Configuration Files\\CPC Customization\\CPCbylayers.scr")

(princ)
)
