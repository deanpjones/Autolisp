;??????????????????????????????????????????
;Arguments (opt 1 or 2, 1-by select, 2-blkname "rev-blk" (nil or name required)
;Returns the entity name.
(defun MYBLK (opt blkname)
	(cond
((= 1 opt)(setq en (ssname (setq ss (ssget ":S" (list (cons 0 "INSERT")))) 0)))
((= 2 opt)(setq en (ssname (setq ss (ssget "X" (list (cons 0 "INSERT")(cons 2 blkname)))) 0)))
(T nil)
	);END COND.
);END DEFUN.

;(myblk 2 "CPC_A1TBLK")
;(entget (myblk 2 "CPC_A1TBLK"))
;(assoc 1 (entget (myblk 2 "CPC_A1TBLK")))
;??????????????????????????????????????????
(defun MYATTRIB (myblk  / )
(setq endxf (entget en))
	(if (= (cdr (assoc 66 endxf)) 1)
	(progn
		(while (/= (cdr (assoc 0 endxf)) "SEQEND")
(setq en (entnext en))(setq endxf (entget en))
;--------------------------------------------------------------------------------------
(cond
((= (cdr (assoc 2 endxf)) "TXT") (entmod (subst (cons 1 "howdy") (assoc 1 endxf) endxf)))
(T nil)
)
;--------------------------------------------------------------------------------------
		);END WHILE.
	);END PROGN.
	);END IF.
(command "regenall")
);END DEFUN.
;(myattrib (myblk 1 nil) (princ en))
;(myattrib (myblk 2 "aabbcc") (princ en))
;??????????????????????????????????????????
(defun FUNKAA ()
(cond
((= (cdr (assoc 2 endxf)) "AA") (entmod (subst (cons 1 "howdy") (assoc 1 endxf) endxf)))
(T (alert "hi"))
)
)
;??????????????????????????????????????????
((= (assoc 2 endxf) "AA")(princ "/nI found the AA tag"))
((= (cdr (assoc 2 endxf)) "AA") (entmod (subst (cons 1 "howdy") (assoc 1 endxf) endxf)))
