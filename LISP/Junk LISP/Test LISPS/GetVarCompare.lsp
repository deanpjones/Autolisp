;;; This routine compares environment variables of two sets and returns the differences.
;;; Jan 10, 2005 Courtesy of Dean Jones.


(defun c:comparegetvar (/ lstvar lstret counter lstlngth lstpair lstpaire lstgrp)
;;;Irrelevant files removed from list  'ACADPREFIX 'DCTCUST 'DWGPREFIX 'FONTMAP 'LOGFILENAME 'LOGFILEPATH 'MENUNAME
;;;'SAVEFILEPATH 'SAVENAME 'TEMPPREFIX 'XLOADPATH

;;;List the system variables.
(setq lstvar (list
'ACADLSPASDOC
'ACADVER
'ACISOUTVER
'AFLAGS
'ANGBASE
'ANGDIR
'APBOX
'APERTURE
'AREA
'ATTDIA
'ATTMODE
'ATTREQ
'AUDITCTL
'AUNITS
'AUPREC
'AUTOSNAP
'BACKZ
'BINDTYPE
'BLIPMODE
'CDATE
'CECOLOR
'CELTSCALE
'CELTYPE
'CELWEIGHT
'CHAMFERA
'CHAMFERB
'CHAMFERC
'CHAMFERD
'CHAMMODE
'CIRCLERAD
'CLAYER
'CMDACTIVE
'CMDDIA
'CMDECHO
'CMDNAMES
'CMLJUST
'CMLSCALE
'CMLSTYLE
'COMPASS
'COORDS
'CPLOTSTYLE
'CPROFILE
'CTAB
'CURSORSIZE
'CVPORT
'DATE
'DBMOD
'DCTMAIN
'DEFLPLSTYLE
'DEFPLSTYLE
'DELOBJ
'DEMANDLOAD
'DIASTAT
'DIMADEC
'DIMALT
'DIMALTD
'DIMALTF
'DIMALTRND
'DIMALTTD
'DIMALTTZ
'DIMALTU
'DIMALTZ
'DIMAPOST
'DIMASO
'DIMASZ
'DIMATFIT
'DIMAUNIT
'DIMAZIN
'DIMBLK
'DIMBLK1
'DIMBLK2
'DIMCEN
'DIMCLRD
'DIMCLRE
'DIMCLRT
'DIMDEC
'DIMDLE
'DIMDLI
'DIMDSEP
'DIMEXE
'DIMEXO
'DIMFIT
'DIMFRAC
'DIMGAP
'DIMJUST
'DIMLDRBLK
'DIMLFAC
'DIMLIM
'DIMLUNIT
'DIMLWD
'DIMLWE
'DIMPOST
'DIMRND
'DIMSAH
'DIMSCALE
'DIMSD1
'DIMSD2
'DIMSE1
'DIMSE2
'DIMSHO
'DIMSOXD
'DIMSTYLE
'DIMTAD
'DIMTDEC
'DIMTFAC
'DIMTIH
'DIMTIX
'DIMTM
'DIMTMOVE
'DIMTOFL
'DIMTOH
'DIMTOL
'DIMTOLJ
'DIMTP
'DIMTSZ
'DIMTVP
'DIMTXSTY
'DIMTXT
'DIMTZIN
'DIMUNIT
'DIMUPT
'DIMZIN
'DISPSILH
'DISTANCE
'DONUTID
'DONUTOD
'DRAGMODE
'DRAGP1
'DRAGP2
'DWGCHECK
'DWGCODEPAGE
'DWGNAME
'DWGTITLED
'EDGEMODE
'ELEVATION
'EXPERT
'EXPLMODE
'EXTMAX
'EXTMIN
'EXTNAMES
'FACETRATIO
'FACETRES
'FILEDIA
'FILLETRAD
'FILLMODE
'FONTALT
'FRONTZ
'FULLOPEN
'GRIDMODE
'GRIDUNIT
'GRIPBLOCK
'GRIPCOLOR
'GRIPHOT
'GRIPS
'GRIPSIZE
'HANDLES
'HIDEPRECISION
'HIGHLIGHT
'HPANG
'HPBOUND
'HPDOUBLE
'HPNAME
'HPSCALE
'HPSPACE
'HYPERLINKBASE
'IMAGEHLT
'INDEXCTL
'INETLOCATION
'INSBASE
'INSNAME
'INSUNITS
'INSUNITSDEFSOURCE
'INSUNITSDEFTARGET
'ISAVEBAK
'ISAVEPERCENT
'ISOLINES
'LASTANGLE
'LASTPOINT
'LASTPROMPT
'LAYOUTREGENCTL
'LENSLENGTH
'LIMCHECK
'LIMMAX
'LIMMIN
'LISPINIT
'LOCALE
'LOGFILEMODE
'LOGINNAME
'LTSCALE
'LUNITS
'LUPREC
'LWDEFAULT
'LWDISPLAY
'LWUNITS
'MAXACTVP
'MAXSORT
'MBUTTONPAN
'MEASUREINIT
'MEASUREMENT
'MENUCTL
'MENUECHO
'MIRRTEXT
'MODEMACRO
'MTEXTED
'NOMUTT
'OFFSETDIST
'OFFSETGAPTYPE
'OLEHIDE
'OLEQUALITY
'OLESTARTUP
'ORTHOMODE
'OSMODE
'OSNAPCOORD
'PAPERUPDATE
'PDMODE
'PDSIZE
'PELLIPSE
'PERIMETER
'PFACEVMAX
'PICKADD
'PICKAUTO
'PICKBOX
'PICKDRAG
'PICKFIRST
'PICKSTYLE
'PLATFORM
'PLINEGEN
'PLINETYPE
'PLINEWID
'PLOTID
'PLOTROTMODE
'PLOTTER
'PLQUIET
'POLARADDANG
'POLARANG
'POLARDIST
'POLARMODE
'POLYSIDES
'POPUPS
'PROJECTNAME
'PROJMODE
'PROXYGRAPHICS
'PROXYNOTICE
'PROXYSHOW
'PROXYWEBSEARCH
'PSLTSCALE
'PSPROLOG
'PSQUALITY
'PSTYLEMODE
'PSTYLEPOLICY
'PSVPSCALE
'PUCSBASE
'QTEXTMODE
'RASTERPREVIEW
'REFEDITNAME
'REGENMODE
'REMEMBERFOLDERS
'RTDISPLAY
'SAVEFILE
'SAVETIME
'SCREENBOXES
'SCREENMODE
'SCREENSIZE
'SDI
'SHADEDGE
'SHADEDIF
'SHORTCUTMENU
'SHPNAME
'SKETCHINC
'SKPOLY
'SNAPANG
'SNAPBASE
'SNAPISOPAIR
'SNAPMODE
'SNAPSTYL
'SNAPTYPE
'SNAPUNIT
'SOLIDCHECK
'SORTENTS
'SPLFRAME
'SPLINESEGS
'SPLINETYPE
'STARTUPTODAY
'SURFTAB1
'SURFTAB2
'SURFTYPE
'SURFU
'SURFV
'SYSCODEPAGE
'TABMODE
'TARGET
'TDCREATE
'TDINDWG
'TDUCREATE
'TDUPDATE
'TDUSRTIMER
'TDUUPDATE
'TEXTEVAL
'TEXTFILL
'TEXTQLTY
'TEXTSIZE
'TEXTSTYLE
'THICKNESS
'TILEMODE
'TOOLTIPS
'TRACEWID
'TRACKPATH
'TREEDEPTH
'TREEMAX
'TRIMMODE
'TSPACEFAC
'TSPACETYPE
'TSTACKALIGN
'TSTACKSIZE
'UCSAXISANG
'UCSBASE
'UCSFOLLOW
'UCSICON
'UCSNAME
'UCSORG
'UCSORTHO
'UCSVIEW
'UCSVP
'UCSXDIR
'UCSYDIR
'UNDOCTL
'UNDOMARKS
'UNITMODE
'VIEWCTR
'VIEWDIR
'VIEWMODE
'VIEWSIZE
'VIEWTWIST
'VISRETAIN
'VSMAX
'VSMIN
'WHIPARC
'WMFBKGND
'WMFFOREGND
'WORLDUCS
'WORLDVIEW
'WRITESTAT
'XCLIPFRAME
'XEDIT
'XFADECTL
'XLOADCTL
'XREFCTL
'ZOOMFACTOR
))

;;;;;;;;;;;;;;;;;;;;;;;;;;;;;;;;;;;;;;;;;;;;;;;;;;;;;;;;;;;;;;;;;;;;;;;;;;;;;;;;;;;
;;;Saves length of variables in lstvar.
(setq lstlngth (length lstvar))

;;;;;;;;;;;;;;;;;;;;;;;;;;;;;;;;;;;;;;;;;;;;;;;;;;;;;;;;;;;;;;;;;;;;;;;;;;;;;;;;;;;
;;;Lists the return values of all system variables.

(setq lstret
	(mapcar '(lambda (x) 
		(getvar x)
		)
	lstvar
	)
)


;;;;;;;;;;;;;;;;;;;;;;;;;;;;;;;;;;;;;;;;;;;;;;;;;;;;;;;;;;;;;;;;;;;;;;;;;;;;;;;;;;;
;;;Groups the system variable (lstvar) with the return value (lstret).

(setq counter 0)
(repeat lstlngth

	(setq lstpair (cons (nth counter lstvar) (nth counter lstret)))
	(setq lstgrp (cons lstpair lstgrp))

(setq counter (1+ counter))
)

;;;;;;;;;;;;;;;;;;;;;;;;;;;;;;;;;;;;;;;;;;;;;;;;;;;;;;;;




;;;(setq lstgrp (element 1 of lstvar and make dotted pair with element 1 of lstret))
;;;(loop this until it returns the entire environment set)
;;;(organize by returning after each dotted pair)

(princ)

)
