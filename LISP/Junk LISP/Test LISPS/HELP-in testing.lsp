(startapp "\"P:\\Riseball Enterprises\\7 - AutoCAD Help\\hh.exe\"" "\"P:\\Riseball Enterprises\\7 - AutoCAD Help\\acad_alr.chm\"")

(vl-registry-write
"HKEY_LOCAL_MACHINE\\SOFTWARE\\Microsoft\\HTMLHelp\\1.x\\ HHRestrictions"
"MaxAllowedZone" 1)
(vl-registry-write
"HKEY_LOCAL_MACHINE\\SOFTWARE\\Microsoft\\HTMLHelp\\1.x\\ HHRestrictions"
"EnableFrameNavigationInSafeMode" 1)
(vl-registry-write
"HKEY_LOCAL_MACHINE\\SOFTWARE\\Microsoft\\HTMLHelp\\1.x\\ ItssRestrictions"
"MaxAllowedZone" 1)


"\"P:\\Riseball Enterprises\\7 - AutoCAD Help\\acad_alr.chm\""

"\"my stuff.txt\"")
