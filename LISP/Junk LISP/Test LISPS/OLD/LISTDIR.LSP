(setq a (vl-directory-files "R:/CADDSupport/Client Standards/(Project Listings)" nil 1)
)

(foreach (vl-filename-base "R:/CADDSupport/Client Standards/(Project Listings)")



R:/CADDSupport/Client Standards/(Project Listings)
