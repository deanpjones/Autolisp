(vl-file-rename "C:/_Configuration/2-AutoLisp/Proposed Lisp/Reactors/text.txt"
		"C:/_Configuration/2-AutoLisp/Proposed Lisp/Reactors/word.txt")
(vl-file-rename "C:/_Configuration/2-AutoLisp/Proposed Lisp/Reactors/word.txt"
		"C:/_Configuration/2-AutoLisp/Proposed Lisp/Reactors/text.txt")
