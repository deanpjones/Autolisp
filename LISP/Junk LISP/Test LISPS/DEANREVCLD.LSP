(defun c:revclouddj (/ pt1 pt2 pt3)




(while
(command "arc" (getpoint) (getpoint) (getpoint))

)

(princ)
)


;;;needs start and end needs to be calculated for points
;;;if points are needed.
(0 . "ARC")
