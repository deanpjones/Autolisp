;To automatically update the revision as specified below.
;Dean Jones Jun 10, 2008
;NEXTREV 08.03.28 ADDED CPC DRAWING NUMBER DJ
;**********************************************************************************************
;**********************************************************************************************
;**********************************************************************************************
(defun C:REVUPISO (/ mydate mydescr myinit att1 att1dxf tag1 val1 attxdxf tagx valx newrevno chknewrevno chkmydate chkmydescr chkmyinit)
(setq myfilter '((0 . "INSERT")(66 . 1)(2 . "Titleblock")))
;********************************
(defun MYBLK (myfilter /)
(ssname (ssget "X" myfilter) 0)
)
;**********************************************************************
(setq mydate "08.03.28" mydescr "ADDED CPC DRAWING NUMBER" myinit "DJ")
;**********************************************************************
(setq att1 (entnext (MYBLK myfilter)))(setq att1dxf (entget att1)) ;ATTRIB TAG DXF

;-------------------------------------------------------------------
;Must set first ATTRIB info here.
(setq tag1 (cdr (assoc 3 att1dxf)))(setq val1 (cdr (assoc 1 att1dxf)))
(if (= tag1 "PLANT_NUMBER") (setq plantno val1))
;-------------------------------------------------------------------
;-------------------------------------------------------------------
;------------------------------------------------------
(setq chknewrevno 0 chkmydate 0 chkmydescr 0 chkmyinit 0)
;------------------------------------------------------

	(while (/= (cdr (assoc 0 att1dxf)) "SEQEND")

;------------------------------------------------------
(setq att1 (entnext att1))(setq attxdxf (entget att1));scroll thru attribs.(NOTE THIS LINE MUST SAVE OVER ITSELF TO REACH THE NEXT ENTITY WHILE LOOPING)
(setq tagx (cdr (assoc 3 attxdxf)))(setq valx (cdr (assoc 1 attxdxf)));return tag and values.
;------------------------------------------------------

	(cond
		((= tagx "REV")
	(progn
(setq newrevno (itoa (1+ (atoi valx))))
	(if (wcmatch valx "#*")
(entmod (subst (cons 1 newrevno) (assoc 1 attxdxf) attxdxf))
(entmod (subst (cons 1 newrevno) (assoc 1 attxdxf) attxdxf))
	);end IF.
	);end PROGN.
)


((and (= chknewrevno 0)(= tagx "REVISION NO. (i)")(or (= valx "")(= valx "-")(= valx " "))) (progn (entmod (subst (cons 1 newrevno) (assoc 1 attxdxf) attxdxf))(setq chknewrevno 1)))
((and (= chknewrevno 0)(= tagx "REVISION (ii)")(or (= valx "")(= valx "-")(= valx " "))) (progn (entmod (subst (cons 1 newrevno) (assoc 1 attxdxf) attxdxf))(setq chknewrevno 1)))
((and (= chknewrevno 0)(= tagx "REVISION (iii)")(or (= valx "")(= valx "-")(= valx " "))) (progn (entmod (subst (cons 1 newrevno) (assoc 1 attxdxf) attxdxf))(setq chknewrevno 1)))
((and (= chknewrevno 0)(= tagx "PREVISION (iiii)")(or (= valx "")(= valx "-")(= valx " "))) (progn (entmod (subst (cons 1 newrevno) (assoc 1 attxdxf) attxdxf))(setq chknewrevno 1)))


((and (= chkmyinit 0)(= tagx "REVISED BY")(or (= valx "")(= valx "-")(= valx " "))) (progn (entmod (subst (cons 1 myinit) (assoc 1 attxdxf) attxdxf))(setq chkmyinit 1)))

((and (= chkmydate 0)(= tagx "REVISION DATE")(or (= valx "")(= valx "-")(= valx " "))) (progn (entmod (subst (cons 1 mydate) (assoc 1 attxdxf) attxdxf))(setq chkmydate 1)))

((and (= chkmydescr 0)(= tagx "DESCRIPTION")(or (= valx "")(= valx "-")(= valx " "))) (progn (entmod (subst (cons 1 mydescr) (assoc 1 attxdxf) attxdxf))(setq chkmydescr 1)))


(T nil)
	);end COND.
;------------------------------------------------------
	);end WHILE.
;------------------------------------------------------
;------------------------------------------------------
(command "regenall")
(princ)
);end DEFUN.



;????????????????????????????????????????????????????????????????????????????????????????
;????????????????????????????????????????????????????????????????????????????????????????
Use: (read-prompts "block_name")

(defun read-prompts ( block_name / dat loop en)

(if (setq dat (tblsearch "block" "Titleblock")) (setq en (entget (cdr (assoc -2 dat))) tag_list nil))

	(while en
(if en
(progn
(if (assoc 3 en)
(setq tag_list (append tag_list (list (list
(cdr (assoc 3 en))
(cdr (assoc 1 en))
(cdr (assoc 2 en))
))
)
)
)
)
)
(setq en (entnext (cdr (assoc -1 en))))(setq en (entget en))
(if en (setq en (entget en)))
	);END WHILE.
(reverse(reverse tag_list))
)
;????????????????????????????????????????????????????????????????????????????????????????
;????????????????????????????????????????????????????????????????????????????????????????
(setq en nil)
(if (setq dat (tblsearch "block" "Titleblock")) (setq en (entget (cdr (assoc -2 dat))) tag_list nil))
(while (setq en (entnext (cdr (assoc -1 en))))
(if (= "LINE" (assoc 0 (setq en (entget en))))
(princ (assoc 0 (setq en (entget en))))
)
)



(setq en (entnext (cdr (assoc -1 en))))(setq en (entget en))
;????????????????????????????????????????????????????????????????????????????????????????
;????????????????????????????????????????????????????????????????????????????????????????
