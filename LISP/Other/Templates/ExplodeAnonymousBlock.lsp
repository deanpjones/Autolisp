(defun C:CCC (/ NewStr sel OLDCMD Namlst entlst str1 str2)
  (setq NewStr (getstring "\nPlease enter a string:")) ;for example,enter "TEMP"
  (if (setq sel (ssget '((0 . "INSERT"))))
    (progn
      (setq OLDCMD (getvar "CMDECHO"))
      (setvar "CMDECHO" 0)
      (setq Namlst (get-name sel))
      ;;(setq Namlst (tblname "BLOCK"))
      (setq entlst (batch-rename-1 Namlst))
      (command ".audit" "Y")
      (batch-rename-2 entlst NewStr)
      (setq str1 (itoa (length Namlst)))
      (setq str2 " have been renamed.")
      (princ (strcat "\n" str1 " blocks" str2))
      (setvar "CMDECHO" OLDCMD)
    )
  )
  (princ)
)
;;;batch rename anonymous block
(defun batch-rename-1 (sstbl / i ent lst new elst)
  (setq i 0)
  (foreach n sstbl
    (setq ent (tblobjname "BLOCK" n))
    (setq ent (cdr (assoc 330 (entget ent))))
    (setq lst (entget ent))
    (setq New (vl-string-subst (itoa i) "*" n))
    (setq lst (subst (cons 2 New) (assoc 2 lst) lst))
    (entmod lst)
    (setq elst (cons ent elst))
    (setq i (1+ i))
  )
  (reverse elst)
)
;;;After All have been audited,batch rename block
(defun batch-rename-2 (blocks appName / i lst New)
  (setq i 0)
  (foreach n blocks
    (setq lst (entget n))
    (setq New (strcat appName "-" (itoa i)))
    (setq lst (subst (cons 2 New) (assoc 2 lst) lst))
    (entmod lst)
    (setq i (1+ i))
  )
)
;;; get all the name of blocks from selections
(defun get-name (ss / i ent lst name nlst)
  (setq i 0)
  (repeat (sslength ss)
    (setq Ent (ssname ss i))
    (setq lst (entget ent))
    (setq name (cdr (assoc 2 lst)))
    (if (and (= (substr name 1 2) "*U") (not (member name Nlst)))
      (setq  Nlst (cons name Nlst))
    )
    (setq i (1+ i))
  )
  (reverse Nlst)
)
;;; get all anonymous blocks
(defun tblname (tblsym / n1 name namlst)
  (setq namlst nil)
  (if (setq n1 (cdr (assoc 2 (tblnext tblsym T))))
    (progn
      (if (= (substr n1 1 2) "*U")
        (setq namlst (cons n1 namlst))
      )
      (while (setq name (cdr (assoc 2 (tblnext tblsym))))
        (if (= (substr name 1 2) "*U")
          (setq namlst (cons name namlst))
	)
      )
    )
  )
  (reverse namlst)
)
