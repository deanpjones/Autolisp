;Compares the dwglst with the oldDwgNo to the newDwgNo and automatically does a saveas to the new name.
;Dean Jones, May 02, 2008.

;Open drawing file
;Run "mySaveAs" to rename file.
;Insert CPC DWG # block with filename field.
;Run "CF" (Convert-Field-Text.lsp) to convert field to text.
;Fix Plot Layout.
;Update revision "ADDED CPC DRAWING NUMBER", change revision to a number.
;Update Drawing List with revision #.

(defun C:mySaveAs (/ oldDwgNo dwglst newNo newDwgNo)

(setq oldDwgNo (vl-string-right-trim ".dwg" (getvar "dwgname")))

;Current list from RBR-000-LST-010-0001 as of May 02, 2008.
(setq dwglst (list
"A-BLOWOUT-1"		"RBR-000-STD-000-0001"
"02-009-100-100-01"	"RBR-000-PLO-020-0001"
"02-009-931-100-53"	"RBR-000-GTH-000-0002"
"02-009-304-100-01"	"RBR-000-SUP-040-0001"
"02-009-510-100-02"	"RBR-000-GTH-000-0003"
"02-009-510-100-03"	"RBR-000-GTH-000-0004"
"02-009-510-100-04"	"RBR-000-GTH-000-0005"
"02-009-600-101-32"	"RBR-000-ISO-000-0001"
"02-009-600-101-42"	"RBR-000-ISO-000-0002"
"02-009-600-102-62"	"RBR-000-ISO-000-0003"

"02-009-010-100-01"	"RBR-000-PID-010-0001"

"02-009-501-101-01"	"RBR-000-PPL-011-0001"
"02-009-501-101-02"	"RBR-000-ARC-000-0001"
"02-009-501-101-03"	"RBR-000-FDN-020-0001"
"02-009-600-101-01"	"RBR-000-ISO-000-0004"
"02-009-600-101-02"	"RBR-000-ISO-000-0005"
"02-009-600-101-03"	"RBR-000-ISO-000-0006"

"02-009-501-102-01"	"RBR-000-PPL-011-0002"
"02-009-501-102-02"	"RBR-000-ARC-000-0002"
"02-009-501-102-03"	"RBR-000-FDN-020-0002"
"02-009-600-102-01"	"RBR-000-ISO-000-0007"
"02-009-600-102-02"	"RBR-000-ISO-000-0008"

"02-009-010-103-01"	"RBR-000-PID-010-0002"

"02-009-304-103-01"	"RBR-000-SUP-040-0002"

"02-009-304-103-03"	"RBR-000-ARC-000-0003"
"02-009-501-103-01"	"RBR-000-PPL-011-0003"
"02-009-600-103-01"	"RBR-000-ISO-000-0009"
"02-009-600-103-02"	"RBR-000-ISO-000-0010"
"02-009-600-103-03"	"RBR-000-ISO-000-0011"
"02-009-600-103-04"	"RBR-000-ISO-000-0012"
"02-009-600-103-05"	"RBR-000-ISO-000-0013"

"02-009-010-104-01"	"RBR-000-PID-010-0003"
"02-009-201-104-01"	"RBR-000-FDN-020-0003"
"02-009-401-104-20"	"RBR-000-SUP-040-0003"
"02-009-401-104-10"	"RBR-000-PPL-011-0004"
"02-009-401-104-40"	"RBR-000-ARC-000-0004"
"02-009-600-104-01"	"RBR-000-ISO-000-0014"
"02-009-600-104-32"	"RBR-000-ISO-000-0015"
"02-009-600-104-42"	"RBR-000-ISO-000-0016"
"02-009-600-104-62"	"RBR-000-ISO-000-0017"

"02-009-100-200-01"	"RBR-000-PLO-020-0002"
"02-009-401-200-20"	"RBR-000-SUP-040-0004"
"02-009-401-200-21"	"RBR-000-ARC-000-0005"


"02-009-010-201-01"	"RBR-000-PID-010-0005"
"02-009-401-201-01"	"RBR-000-PPL-011-0005"


"02-009-010-202-01"	"RBR-000-PID-010-0006"
"02-009-401-202-01"	"RBR-000-PPL-011-0006"


"02-009-010-203-01"	"RBR-000-PID-010-0007"
"02-009-401-203-01"	"RBR-000-PPL-011-0007"


"02-009-010-204-01"	"RBR-000-PID-010-0008"
"02-009-401-204-01"	"RBR-000-PPL-011-0008"
"02-009-401-204-20"	"RBR-000-SUP-040-0005"
"02-009-401-204-21"	"RBR-000-ARC-000-0006"


"02-009-010-301-01"	"RBR-000-PID-010-0009"
"02-009-304-301-01"	"RBR-000-SUP-040-0006"
"02-009-304-301-02"	"RBR-000-ARC-000-0007"
"02-009-501-301-01"	"RBR-000-PPL-011-0009"
"02-009-600-301-01"	"RBR-000-ISO-000-0019"
"02-009-600-301-02"	"RBR-000-ISO-000-0020"
"02-009-600-301-03"	"RBR-000-ISO-000-0021"
"02-009-600-301-04"	"RBR-000-ISO-000-0022"
"02-009-600-301-05"	"RBR-000-ISO-000-0023"
"02-009-600-301-06"	"RBR-000-ISO-000-0024"
"02-009-600-301-07"	"RBR-000-ISO-000-0025"


"02-009-010-302-01"	"RBR-000-PID-010-0010"
"02-009-304-302-01"	"RBR-000-SUP-040-0007"
"02-009-304-302-02"	"RBR-000-ARC-000-0008"
"02-009-501-302-01"	"RBR-000-PPL-011-0010"
"02-009-600-302-01"	"RBR-000-ISO-000-0026"
"02-009-600-302-02"	"RBR-000-ISO-000-0027"


"02-009-010-303-01"	"RBR-000-PID-010-0011"
"02-009-304-303-01"	"RBR-000-SUP-040-0008"
"02-009-304-303-02"	"RBR-000-ARC-000-0009"
"02-009-501-303-01"	"RBR-000-PPL-011-0011"
"02-009-600-303-01"	"RBR-000-ISO-000-0028"
"02-009-600-303-02"	"RBR-000-ISO-000-0029"
"02-009-600-303-03"	"RBR-000-ISO-000-0030"
"02-009-600-303-04"	"RBR-000-ISO-000-0031"
"02-009-600-303-05"	"RBR-000-ISO-000-0032"
"02-009-600-303-06"	"RBR-000-ISO-000-0033"
"02-009-600-303-07"	"RBR-000-ISO-000-0034"
"02-009-600-303-08"	"RBR-000-ISO-000-0035"


"02-009-010-304-01"	"RBR-000-PID-010-0012"
"02-009-304-304-01"	"RBR-000-SUP-040-0009"
"02-009-304-304-02"	"RBR-000-ARC-000-0010"
"02-009-501-304-01"	"RBR-000-PPL-011-0012"
"02-009-600-304-01"	"RBR-000-ISO-000-0036"
"02-009-600-304-02"	"RBR-000-ISO-000-0037"
"02-009-600-304-03"	"RBR-000-ISO-000-0038"
"02-009-600-304-04"	"RBR-000-ISO-000-0039"
"02-009-600-304-05"	"RBR-000-ISO-000-0040"


"02-009-010-305-01"	"RBR-000-PID-010-0013"
"02-009-304-305-01"	"RBR-000-SUP-040-0010"
"02-009-304-305-02"	"RBR-000-ARC-000-0011"
"02-009-501-305-01"	"RBR-000-PPL-011-0013"
"02-009-600-305-01"	"RBR-000-ISO-000-0041"
"02-009-600-305-02"	"RBR-000-ISO-000-0042"
"02-009-600-305-03"	"RBR-000-ISO-000-0043"
"02-009-600-305-04"	"RBR-000-ISO-000-0044"
"02-009-600-305-05"	"RBR-000-ISO-000-0045"
"02-009-600-305-06"	"RBR-000-ISO-000-0046"
"02-009-600-305-07"	"RBR-000-ISO-000-0047"
"02-009-600-305-08"	"RBR-000-ISO-000-0048"


"02-009-010-306-01"	"RBR-000-PID-010-0014"
"02-009-304-306-01"	"RBR-000-SUP-040-0011"
"02-009-304-306-02"	"RBR-000-ARC-000-0012"
"02-009-501-306-01"	"RBR-000-PPL-011-0014"
"02-009-600-306-01"	"RBR-000-ISO-000-0049"
"02-009-600-306-02"	"RBR-000-ISO-000-0050"
"02-009-600-306-03"	"RBR-000-ISO-000-0051"
"02-009-600-306-04"	"RBR-000-ISO-000-0052"
"02-009-600-306-05"	"RBR-000-ISO-000-0053"
"02-009-600-306-06"	"RBR-000-ISO-000-0054"
"02-009-600-306-07"	"RBR-000-ISO-000-0055"
"02-009-600-306-08"	"RBR-000-ISO-000-0056"
"02-009-600-306-09"	"RBR-000-ISO-000-0057"
"02-009-600-306-10"	"RBR-000-ISO-000-0058"
"02-009-600-306-11"	"RBR-000-ISO-000-0059"
"02-009-600-306-12"	"RBR-000-ISO-000-0060"


"02-009-010-307-01"	"RBR-000-PID-010-0015"
"02-009-304-307-01"	"RBR-000-SUP-040-0012"
"02-009-304-307-02"	"RBR-000-ARC-000-0013"
"02-009-501-307-01"	"RBR-000-PPL-011-0015"
"02-009-600-307-01"	"RBR-000-ISO-000-0061"
"02-009-600-307-02"	"RBR-000-ISO-000-0062"
"02-009-600-307-03"	"RBR-000-ISO-000-0063"
"02-009-600-307-04"	"RBR-000-ISO-000-0064"
"02-009-600-307-05"	"RBR-000-ISO-000-0065"
"02-009-600-307-06"	"RBR-000-ISO-000-0066"
"02-009-600-307-07"	"RBR-000-ISO-000-0067"
"02-009-600-307-08"	"RBR-000-ISO-000-0068"
"02-009-600-307-09"	"RBR-000-ISO-000-0069"
"02-009-600-307-10"	"RBR-000-ISO-000-0070"


"02-009-010-308-01"	"RBR-000-PID-010-0016"
"02-009-304-308-01"	"RBR-000-FDN-020-0004"
"02-009-501-308-01"	"RBR-000-PPL-011-0016"


"02-009-010-309-01"	"RBR-000-PID-010-0017"
"02-009-304-309-01"	"RBR-000-FDN-020-0005"
"02-009-501-309-01"	"RBR-000-PPL-011-0017"


"02-009-010-310-01"	"RBR-000-PID-010-0018"
"02-009-304-310-01"	"RBR-000-FDN-020-0006"
"02-009-501-310-01"	"RBR-000-PPL-011-0018"


"02-009-001-401-01"	"RBR-000-PFD-000-0001"
"02-009-100-401-01"	"RBR-000-PLO-020-0003"
"02-009-010-401-01"	"RBR-000-PID-010-0020"
"02-009-501-401-01"	"RBR-000-PPL-011-0020"
"02-009-501-401-03"	"RBR-000-PPL-011-0021"


"02-009-010-402-01"	"RBR-000-PID-010-0021"
"02-009-201-402-01"	"RBR-000-FDN-020-0008"
"02-009-501-402-01"	"RBR-000-PPL-011-0022"


"02-009-010-403-01"	"RBR-000-PID-010-0022"
"02-009-201-403-01"	"RBR-000-FDN-020-0009"
"02-009-501-403-01"	"RBR-000-PPL-011-0023"


"02-009-100-500-01"	"RBR-000-PLO-020-0004"
"02-009-401-500-20"	"RBR-000-SUP-040-0013"
"02-009-501-500-01"	"RBR-000-PPL-011-0024"


"02-009-010-501-01"	"RBR-000-PID-010-0023"
"02-009-401-501-01"	"RBR-000-PPL-011-0025"
"02-009-600-501-01"	"RBR-000-ISO-000-0071"


"02-009-010-502-01"	"RBR-000-PID-010-0024"
"02-009-401-502-01"	"RBR-000-PPL-011-0026"
"02-009-600-502-01"	"RBR-000-ISO-000-0072"
))

;Search list and return new drawing number.
(if (/= nil (member oldDwgNo dwglst))
	(progn
(setq newNo (cadr (member oldDwgNo dwglst)))
(setq newDwgNo (strcat newNo ".dwg"))
(vla-saveas (vla-get-ActiveDocument (vlax-get-Acad-Object)) (strcat (getvar "dwgprefix") newDwgNo))
	)
(princ "/nThere is now match")
)

(princ)
)
