(defun ax:plot (device ctb paper origin / acadobj docobj actlay)
(setq acadobj (vlax-get-acad-object)
docobj (vla-get-activedocument acadobj)
actlay (vla-get-activelayout docobj)
)
(foreach itm
(list
(list 'vlax-invoke-method actlay 'RefreshPlotDeviceInfo)
(list 'vla-put-Configname actlay device)
(list 'vla-put-StyleSheet actlay ctb)
(list 'vla-put-CanonicalMediaName actlay (acet-str-replace " " "_"
paper))
(list 'vla-put-CenterPlot actlay :vlax-false)
(list 'vla-put-PaperUnits actlay acInches)
(list 'vla-put-PlotHidden actlay :vlax-false)
(list 'vla-put-PlotRotation actlay ac90degrees)
(list 'vla-put-PlotType actlay acLimits)
(list 'vla-put-PlotOrigin actlay origin)
(list 'vla-put-PlotWithPlotStyles actlay :vlax-true)
(list 'vla-put-ScaleLineweights actlay :vlax-false)
(list 'vla-put-UseStandardScale actlay :vlax-false)
(list 'vla-SetCustomScale actlay 1 48)
)
(setq errobj (vl-catch-all-apply (car itm)(cdr itm)))
)
(vla-PlotToDevice docobj)
(princ)
)
